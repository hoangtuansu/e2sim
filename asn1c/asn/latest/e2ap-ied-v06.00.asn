-- ASN1START 

-- ************************************************************** 

-- E2AP 

-- Information Element Definitions 

--  

-- ************************************************************** 

 

E2AP-IEs { 

iso(1) identified-organization(3) dod(6) internet(1) private(4) enterprise(1) oran(53148) e2(1) version2 (2) e2ap(1) e2ap-IEs (2)} 

 

DEFINITIONS AUTOMATIC TAGS ::=  

 

BEGIN 

 

IMPORTS 

Criticality, 

Presence, 

ProcedureCode, 

ProtocolIE-ID, 

TriggeringMessage 

FROM E2AP-CommonDataTypes 

 

maxnoofErrors, 

maxProtocolIEs 

FROM E2AP-Constants; 

 

-- A 

 

-- ************************************************************** 

-- [New for E2AP v02.00] copied from 3GPP 38.413 (NGAP) IEs  

-- ************************************************************** 

AMFName ::= PrintableString (SIZE(1..150, ...)) 

 

-- B 

-- C 
Cause ::= CHOICE { 

ricRequest   CauseRICrequest, 

ricService   CauseRICservice, 

e2Node    CauseE2node, 

transport   CauseTransport, 

protocol   CauseProtocol, 

misc    CauseMisc, 

... 

} 

 

CauseE2node ::= ENUMERATED { 

e2node-component-unknown, 

... 

} 

 

CauseMisc ::= ENUMERATED { 

control-processing-overload, 

hardware-failure, 

om-intervention, 

unspecified, 

... 

} 

 

CauseProtocol ::= ENUMERATED { 

transfer-syntax-error, 

abstract-syntax-error-reject, 

abstract-syntax-error-ignore-and-notify, 

message-not-compatible-with-receiver-state, 

semantic-error, 

abstract-syntax-error-falsely-constructed-message, 

unspecified, 

... 

} 

 

CauseRICrequest ::= ENUMERATED { 

ran-function-id-invalid,  

action-not-supported,  

excessive-actions, 

duplicate-action,  

duplicate-event-trigger, 

function-resource-limit,  

request-id-unknown,  

inconsistent-action-subsequent-action-sequence,  

control-message-invalid,  

ric-call-process-id-invalid, 

control-timer-expired, 

control-failed-to-execute, 

system-not-ready, 

unspecified, 

... , 

ric-subscription-end-time-expired, 

ric-subscription-end-time-invalid, 

duplicate-ric-request-id, 

eventTriggerNotSupported, 

requested-information-unavailable, 

invalid-information-request 

} 

 

CauseRICservice ::= ENUMERATED{ 

ran-function-not-supported,  

excessive-functions,  

ric-resource-limit, 

... 

} 

CauseTransport ::= ENUMERATED { 

unspecified, 

transport-resource-unavailable, 

... 

} 

 

-- ************************************************************** 

-- copied from 3GPP 38.413 (NGAP) IEs  

-- note: ie-Extensions removed 

-- ************************************************************** 

CriticalityDiagnostics ::= SEQUENCE { 

procedureCode     ProcedureCode       OPTIONAL, 

triggeringMessage    TriggeringMessage      OPTIONAL, 

procedureCriticality   Criticality        OPTIONAL, 

ricRequestorID     RICrequestID       OPTIONAL, 

iEsCriticalityDiagnostics  CriticalityDiagnostics-IE-List   OPTIONAL, 

... 

} 

 

CriticalityDiagnostics-IE-List ::= SEQUENCE (SIZE(1..maxnoofErrors)) OF CriticalityDiagnostics-IE-Item 

 

CriticalityDiagnostics-IE-Item ::= SEQUENCE { 

iECriticality  Criticality, 

iE-ID    ProtocolIE-ID, 

typeOfError   TypeOfError, 

... 

} 

 

-- D 

-- E 

 

-- Following IE used to carry 3GPP defined SETUP and RAN Configuration messages defined in F1AP, E1AP, XnAP, etc. 

E2nodeComponentConfiguration ::= SEQUENCE{ 

e2nodeComponentRequestPart  OCTET STRING, 

e2nodeComponentResponsePart  OCTET STRING, 

... 

} 

 

E2nodeComponentConfigurationAck ::= SEQUENCE{ 

updateOutcome  ENUMERATED {success, failure, ...}, 

failureCause  Cause   OPTIONAL, 

... 

} 

 

E2nodeComponentInterfaceType ::= ENUMERATED {ng, xn, e1, f1, w1, s1, x2,...} 

 

E2nodeComponentID ::= CHOICE{ 

e2nodeComponentInterfaceTypeNG E2nodeComponentInterfaceNG, 

e2nodeComponentInterfaceTypeXn E2nodeComponentInterfaceXn, 

e2nodeComponentInterfaceTypeE1 E2nodeComponentInterfaceE1, 

e2nodeComponentInterfaceTypeF1 E2nodeComponentInterfaceF1, 

e2nodeComponentInterfaceTypeW1 E2nodeComponentInterfaceW1, 

e2nodeComponentInterfaceTypeS1 E2nodeComponentInterfaceS1, 

e2nodeComponentInterfaceTypeX2 E2nodeComponentInterfaceX2, 

... 

} 

 

E2nodeComponentInterfaceE1 ::= SEQUENCE{ 

gNB-CU-UP-ID  GNB-CU-UP-ID, 

... 

} 
E2nodeComponentInterfaceF1 ::= SEQUENCE{ 

gNB-DU-ID   GNB-DU-ID, 

... 

} 

 

E2nodeComponentInterfaceNG ::= SEQUENCE{ 

amf-name   AMFName, 

... 

} 

 

E2nodeComponentInterfaceS1 ::= SEQUENCE{ 

mme-name   MMEname, 

... 

} 

 

E2nodeComponentInterfaceX2 ::= SEQUENCE{ 

global-eNB-ID  GlobalENB-ID OPTIONAL, 

global-en-gNB-ID GlobalenGNB-ID OPTIONAL, 

... 

} 

 

E2nodeComponentInterfaceXn ::= SEQUENCE{ 

global-NG-RAN-Node-ID  GlobalNG-RANNode-ID, 

... 

} 

 

E2nodeComponentInterfaceW1 ::= SEQUENCE{ 

ng-eNB-DU-ID  NGENB-DU-ID, 

... 

} 

 

-- ************************************************************** 

-- copied from 3GPP 36.423 (X2AP) IEs 

-- note: ie-Extensions removed 

-- ************************************************************** 

ENB-ID ::= CHOICE { 

macro-eNB-ID   BIT STRING (SIZE (20)), 

home-eNB-ID    BIT STRING (SIZE (28)), 

... , 

short-Macro-eNB-ID  BIT STRING (SIZE(18)), 

long-Macro-eNB-ID  BIT STRING (SIZE(21)) 

} 

-- ************************************************************** 

-- copied from 3GPP 38.423 (XnAP) IEs  

-- note: choice-extension removed 

-- ************************************************************** 

ENB-ID-Choice ::= CHOICE { 

enb-ID-macro   BIT STRING (SIZE(20)), 

enb-ID-shortmacro  BIT STRING (SIZE(18)), 

enb-ID-longmacro  BIT STRING (SIZE(21)), 

... 

} 

 

-- ************************************************************** 

-- copied from 3GPP 36.423 (X2AP) IEs 

-- note: ie-Extensions removed 

-- Note: to avoid duplicate names with XnAP, GNB-ID renamed ENGNB-ID, GlobalGNB-ID renamed GlobalenGNB-ID 

-- ************************************************************** 

ENGNB-ID ::= CHOICE { 

gNB-ID BIT STRING (SIZE (22..32)), 

... 

} 
-- F 

-- G 

GlobalE2node-ID ::= CHOICE{ 

gNB     GlobalE2node-gNB-ID, 

en-gNB    GlobalE2node-en-gNB-ID, 

ng-eNB    GlobalE2node-ng-eNB-ID, 

eNB     GlobalE2node-eNB-ID, 

... 

} 

 

GlobalE2node-en-gNB-ID ::= SEQUENCE{ 

global-en-gNB-ID GlobalenGNB-ID, 

en-gNB-CU-UP-ID  GNB-CU-UP-ID OPTIONAL, 

en-gNB-DU-ID  GNB-DU-ID  OPTIONAL, 

... 

} 

GlobalE2node-eNB-ID ::= SEQUENCE{ 

global-eNB-ID  GlobalENB-ID, 

... 

} 

GlobalE2node-gNB-ID ::= SEQUENCE{ 

global-gNB-ID  GlobalgNB-ID, 

global-en-gNB-ID GlobalenGNB-ID OPTIONAL, 

gNB-CU-UP-ID  GNB-CU-UP-ID OPTIONAL, 

gNB-DU-ID   GNB-DU-ID  OPTIONAL, 

... 

} 

GlobalE2node-ng-eNB-ID ::= SEQUENCE{ 

global-ng-eNB-ID GlobalngeNB-ID, 

global-eNB-ID  GlobalENB-ID OPTIONAL, 

ngENB-DU-ID   NGENB-DU-ID  OPTIONAL, 

... 

} 

-- ************************************************************** 

-- copied from 3GPP 36.423 (X2AP) IEs 

-- note: ie-Extensions removed 

-- ************************************************************** 

 

GlobalENB-ID ::= SEQUENCE { 

pLMN-Identity  PLMN-Identity, 

eNB-ID    ENB-ID, 

... 

} 

-- ************************************************************** 

-- copied from 3GPP 36.423 (X2AP) IEs 

-- Note: to avoid duplicate names with XnAP, GNB-ID renamed ENGNB-ID, GlobalGNB-ID renamed GlobalenGNB-ID 

-- ************************************************************** 

GlobalenGNB-ID ::= SEQUENCE { 

pLMN-Identity  PLMN-Identity, 

gNB-ID    ENGNB-ID, 

... 

} 

-- ************************************************************** 

-- copied from 3GPP 38.423 (XnAP) IEs  

-- note: choice-extension removed 

-- ************************************************************** 

GlobalgNB-ID ::= SEQUENCE { 

plmn-id    PLMN-Identity, 

gnb-id    GNB-ID-Choice, 

... 

} 
-- ************************************************************** 

-- copied from 3GPP 38.423 (XnAP) IEs  

-- note: choice-extension removed 

-- ************************************************************** 

GlobalngeNB-ID ::= SEQUENCE { 

plmn-id   PLMN-Identity, 

enb-id   ENB-ID-Choice, 

... 

} 

 

-- ************************************************************** 

-- [NEW for E2AP v02.00] copied from 3GPP 38.423 (XnAP) IEs  

-- Note: extension field removed 

-- ************************************************************** 

 

GlobalNG-RANNode-ID ::= CHOICE { 

gNB      GlobalgNB-ID, 

ng-eNB     GlobalngeNB-ID, 

... 

} 

 

GlobalRIC-ID ::= SEQUENCE{ 

pLMN-Identity   PLMN-Identity, 

ric-ID     BIT STRING (SIZE (20)), 

... 

} 

 

-- ************************************************************** 

-- copied from 3GPP 37.483 (E1AP) IEs  

-- ************************************************************** 

GNB-CU-UP-ID::=  INTEGER (0..68719476735) 

 

-- ************************************************************** 

-- copied from 3GPP 38.473 (F1AP) IEs  

-- ************************************************************** 

GNB-DU-ID::=   INTEGER (0..68719476735) 

 

-- ************************************************************** 

-- copied from 3GPP 38.423 (XnAP) IEs  

-- note: choice-extension removed 

-- ************************************************************** 

GNB-ID-Choice ::= CHOICE { 

gnb-ID     BIT STRING (SIZE(22..32)), 

... 

} 

-- H 

-- I 

-- J 

-- K 

-- L 

 

ListedRecordsOnly ::=  ENUMERATED {true, ...} 

 

-- M 

 

-- ************************************************************** 

-- [New for E2AP v02.00] copied from 3GPP 36.413 (S1AP) IEs 

-- ************************************************************** 

MMEname ::= PrintableString (SIZE (1..150,...)) 

 

-- N 

 

-- ************************************************************** 

-- copied from 3GPP 37.473 (W1AP) IEs 
-- ************************************************************** 

NGENB-DU-ID ::= INTEGER (0..68719476735) 

 

 

-- O 

-- P 

-- ************************************************************** 

-- copied from 3GPP 36.423 (X2AP) IEs 

-- ************************************************************** 

PLMN-Identity ::= OCTET STRING (SIZE(3)) 

 

-- Q 

-- R 

-- ************************************************************** 

-- Following IE defined in E2SM 

-- ************************************************************** 

RANfunctionDefinition ::= OCTET STRING 

 

RANfunctionID ::= INTEGER (0..4095) 

 

RANfunctionOID ::= PrintableString(SIZE(1..1000,...)) 

 

RANfunctionRevision ::= INTEGER (0..4095) 

 

-- ************************************************************** 

-- Following IE defined in E2SM 

-- ************************************************************** 

RICactionDefinition ::= OCTET STRING 

 

-- new in E2AP-v03.00 

RICactionExecutionOrder ::= INTEGER (0..255, ...) 

 

RICactionID ::= INTEGER (0..255) 

 

RICactionType ::= ENUMERATED{ 

report, 

insert, 

policy, 

... 

} 

 

-- ************************************************************** 

-- Following IE defined in E2SM 

-- ************************************************************** 

RICcallProcessID ::= OCTET STRING 

 

RICcontrolAckRequest ::= ENUMERATED{ 

noAck, 

ack, 

... 

} 

 

-- ************************************************************** 

-- Following IE defined in E2SM 

-- ************************************************************** 

RICcontrolHeader ::= OCTET STRING 

 

-- ************************************************************** 

-- Following IE defined in E2SM 

-- ************************************************************** 

RICcontrolMessage ::= OCTET STRING 

 

-- ************************************************************** 

-- Following IE defined in E2SM 
-- ************************************************************** 

RICcontrolOutcome ::= OCTET STRING 

 

-- ************************************************************** 

-- Following IE defined in E2SM 

-- ************************************************************** 

RICeventTriggerDefinition ::= OCTET STRING 

 

-- ************************************************************** 

-- Following IE defined in E2SM 

-- ************************************************************** 

RICindicationHeader ::= OCTET STRING 

 

-- ************************************************************** 

-- Following IE defined in E2SM 

-- ************************************************************** 

RICindicationMessage ::= OCTET STRING 

 

RICindicationSN ::= INTEGER (0..65535) 

 

RICindicationType ::= ENUMERATED{ 

report, 

insert, 

... 

} 

 

RICrequestID ::= SEQUENCE { 

ricRequestorID    INTEGER (0..65535), 

ricInstanceID    INTEGER (0..65535), 

... 

} 

 

RICsubscriptionTime ::= OCTET STRING (SIZE(8)) 

 

RICsubsequentAction ::=SEQUENCE{ 

ricSubsequentActionType  RICsubsequentActionType, 

ricTimeToWait    RICtimeToWait, 

... 

} 

 

 

RICsubscriptionAuditFlag ::= SEQUENCE{ 

listedRecordsOnly   ListedRecordsOnly   OPTIONAL, 

... 

} 

RICsubsequentActionType ::= ENUMERATED{ 

continue, 

wait, 

... 

} 

 

-- ************************************************************** 

-- Following IE defined in E2SM 

-- ************************************************************** 

RICqueryHeader ::= OCTET STRING 

 

-- ************************************************************** 

-- Following IE defined in E2SM 

-- ************************************************************** 

RICqueryDefinition ::= OCTET STRING 

 

-- ************************************************************** 

-- Following IE defined in E2SM 

-- ************************************************************** 
RICqueryOutcome ::= OCTET STRING 

 

 

RICtimeToWait ::= ENUMERATED{ 

w1ms, 

w2ms, 

w5ms, 

w10ms, 

w20ms, 

w30ms, 

w40ms, 

w50ms, 

w100ms, 

w200ms, 

w500ms, 

w1s, 

w2s, 

w5s, 

w10s, 

w20s, 

w60s, 

... 

} 

-- S 

-- T 

-- ************************************************************** 

-- copied from 3GPP 38.413 (NGAP) IEs 

-- ************************************************************** 

TimeToWait ::= ENUMERATED {v1s, v2s, v5s, v10s, v20s, v60s, ...} 

 

 

TNLinformation ::= SEQUENCE{ 

tnlAddress			BIT STRING (SIZE(1..160,...)), 

tnlPort				BIT STRING (SIZE(16))	OPTIONAL, 

... 

} 

 

TNLusage ::= ENUMERATED{ric-service, support-function, both, ...} 

 

TransactionID ::= INTEGER (0..255,...) 

 

-- ************************************************************** 

-- copied from 3GPP 38.413 (NGAP) IEs 

-- ************************************************************** 

TypeOfError ::= ENUMERATED { 

not-understood, 

missing, 

... 

} 

 

-- U 

-- V 

-- W 

-- X 

-- Y 

-- Z 

 

END 

-- ASN1STOP
